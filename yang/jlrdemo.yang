module jlrdemo {

    namespace "http://feuerlabs.com/jlrdemo";
    prefix demo;

    import exosense {
        prefix exo;
    }

    description
	"JSON-RPC spec for the Jaguar Land Rover demo remote HVAC control." +
	"The protocol will be used between the Exosense Server and the web " +
	"server as well as between the Exosense Device JLR Demo Application " +
	"(JLR App) and the Webkit running the IVI UI in the vehicle.";

    typedef id-string {
      description "Common type for string identifiers in exodm";
      type string {
	length "1..64";
      }
    }

    //
    // Set the temperature in the vehicle
    //
    rpc set-left-temperature-request {
        description
	    "**Set the left cabin temperature**\n\n" +
	    "Webkit -> JLR App.\n\n" +
	    "Webserver -> Exosense Server.\n\n" +
	    "This call instructs the JLR App to emit CAN frames to the HVAC " +
	    "controller that will set the cabin temperature (left and right) to the " +
	    "given Celsius value. \n\n\n\n";

        input {
            description
		"Input consists of standard request elements " +
                "and a left/right temperature value.";

            uses exo:std-request;

	    leaf temperature {
		description "Left side temperature to set. Celsius";
		type uint32;
	    }
	}
        // Output only contains status.
        output {
            description
            "Output sent in response to a get-right-temperature-request";

	    leaf temperature {
		description "Left side temperature to set. Celsius";
		type uint32;
	    }
            uses exo:std-callback;
        }
    }

    //
    // Get the right hand temperature in the vehicle
    //
    rpc get-left-temperature-request {
        description
	    "**Retrieve the left cabin temperature**\n\n" +
	    "Webkit -> JLR App.\n\n" +
	    "Webserver -> Exosense Server.\n\n";

        input {
            uses exo:std-request;
	}

        output {
            description
            "Output sent in response to a set-temperature-request";
	    leaf temperature {
		description "Left side temperature to set. Celsius";
		type uint32;
	    }
            uses exo:std-callback;
        }
    }

    notification get-left-temperature-notification {
	description
	    "Notificaiton sent back in response to get-left-temperature-notification.";

	leaf temperature {
	    description "Temperature celsius";
	    type uint32;
	}
	uses exo:std-callback;
    }

    rpc set-right-temperature-request {
        description
	    "**Set the right cabin temperature**\n\n" +
	    "Webkit -> JLR App.\n\n" +
	    "Webserver -> Exosense Server.\n\n" +
	    "This call instructs the JLR App to emit CAN frames to the HVAC " +
	    "controller that will set the cabin temperature (left and right) to the " +
	    "given Celsius value. \n\n\n\n";

        input {
            description
		"Input consists of standard request elements " +
                "and a left/right temperature value.";

            uses exo:std-request;

	    leaf temperature {
		description "Left side temperature to set. Celsius";
		type uint32;
	    }
	}
        // Output only contains status.
        output {
            description
            "Output sent in response to a set-temperature-request";
            uses exo:std-callback;
        }
    }


    //
    // Get the right hand temperature in the vehicle
     //
    rpc get-right-temperature-request {
        description
	    "**Retrieve the right cabin temperature**\n\n" +
	    "Webkit -> JLR App.\n\n" +
	    "Webserver -> Exosense Server.\n\n";

        input {
            uses exo:std-request;

	}

        output {
            description
            "Output sent in response to a get-right-temperature-request";
	    leaf temperature {
		description "Right side temperature to set. Celsius";
		type uint32;
	    }
            uses exo:std-callback;
        }
    }

    notification get-right-temperature-notification {
	description
	    "Notificaiton sent back in response to get-right-temperature-notification.";

	leaf temperature {
	    description "Temperature celsius";
	    type uint32;
	}
	uses exo:std-callback;
    }

    //
    // Set the HVAC fan speed
    //
    rpc set-fan-speed-request {
        description
	    "**Set the fan speed**\n\n" +
	    "Webkit -> JLR App\n\n" +
	    "Webserver -> Exosense Server\n\n" +
	    "This call instructs the JLR App to emit CAN frames to the HVAC " +
	    "controller that will set the fan speed to the given value.\n\n\n\n";

        input {
            description
		"Input consists of standard request elements " +
                "and a fan speed between 0 and 9.";

            uses exo:std-request;

	    leaf fan-speed {
		description "Fan speed to set. 0 = Off. 9 = Max.";
		type uint32;
	    }
	}

        // Output only contains status.
        output {
            description
            "Output sent in response to a set-fan-speed-request";
            uses exo:std-callback;
        }
    }

    //
    // Get the fan speed in the vehicle
     //
    rpc get-fan-speed-request {
        description
	    "**Retrieve the fan speed**\n\n" +
	    "Webkit -> JLR App.\n\n" +
	    "Webserver -> Exosense Server.\n\n";

        input {
            uses exo:std-request;

	}

        output {
            description
            "Output sent in response to a get-fan-speed-request";
	    leaf fan-speed {
		description "Fan speed 0-15";
		type uint32;
	    }
            uses exo:std-callback;
        }
    }

    notification get-fan-speed-notification {
	description
	    "Notificaiton sent back in response to get-fan-speed-request.";

	leaf fan-speed {
	    description "Fan speed 0-15";
	    type uint32;
	}
	uses exo:std-callback;
    }

    //
    // Set airflow direction
    //
    rpc set-airflow-direction-request {
        description
	    "**Set the airflow direction**\n\n" +
	    "Webkit -> JLR App\n\n" +
	    "Webserver -> Exosense Server\n\n" +
	    "This call instructs the JLR App to emit CAN frames to the HVAC " +
	    "controller that will set the airflow direction to the given value.\n\n\n\n";

        input {
            description
		"Input consists of standard request elements " +
                "and a a direction value of 0-7.";

            uses exo:std-request;

	    leaf direction {
		description "Direction of airflow.\n\n" +
		    "7 	Foot / Face Screen\n\n" +
		    "6 Face / Screen\n\n" +
		    "5 Foot / Screen\n\n" +
		    "4 Screen\n\n" +
		    "3 Foot / Face\n\n" +
		    "2 Face\n\n" +
		    "1 Foot\n\n" +
		    "0 Auton\n\n\n";

		type uint32;
	    }
	}

        // Output only contains status.
        output {
            description
            "Output sent in response to a set-fan-speed-request";
            uses exo:std-callback;
        }
    }

    //
    // Get the current airflow direction
     //
    rpc get-airflow-direction-request {
        description
	    "**Retrieve the airflow**\n\n" +
	    "Webkit -> JLR App.\n\n" +
	    "Webserver -> Exosense Server.\n\n";

        input {
            uses exo:std-request;

	}

        output {
            description
            "Output sent in response to a get-airflow-direction-request";
	    leaf direction {
		description "Direction of airflow.\n\n" +
		    "7 Foot / Face Screen\n\n" +
		    "6 Face / Screen\n\n" +
		    "5 Foot / Screen\n\n" +

		    "3 Foot / Face\n\n" +
		    "2 Face\n\n" +
		    "1 Foot\n\n" +
		    "0 Auton\n\n\n";

		type uint32;
	    }
            uses exo:std-callback;
        }
    }

    notification get-airflow-direction-notification {
	description
	    "Notificaiton sent back in response to get-airflow-direction-notification.";

	leaf direction {
	    description "Direction of airflow.\n\n" +
		"7 Foot / Face Screen\n\n" +
		"6 Face / Screen\n\n" +
		"5 Foot / Screen\n\n" +

		"3 Foot / Face\n\n" +
		"2 Face\n\n" +
		"1 Foot\n\n" +
		"0 Auton\n\n\n";

	    type uint32;
	}

	uses exo:std-callback;
    }

    //
    // Waypoint processor.
    //
    rpc process-waypoints {
        description
	    "**Process a batch of waypoint**\n\n " +
	    "Exosense Server -> Webserver\n\n" +
	    "This call is made to the web server to deliver a number of lat/lon waypoints " +
	    "gathered from the vehicle's GPS receiver.";

        input {
            uses exo:std-request;

	    list waypoints {
                description  "A list of waypoints that the vehicle has passed.";
                key "ts";

		leaf ts {
		    description "UTC Time Stamp";
		    type uint32;
		}

		leaf lat {
		    description "Latitude of device location. Six decimal precision";
		    type decimal64 {
			fraction-digits 6;
			range "-90..90";
		    }
		}

		leaf lon {
		    description "Longitude of device location. Six decimal precision";
		    type decimal64 {
			fraction-digits 6;
			range "-180..180";
		    }
		}
            }
        }

        // Output only contains status.
        output {
            description
		"Output sent in response to a process-waypoints to indicate that the waypoints have been received.";
            leaf result {
		type exo:status-code;
	    }
        }
    }
}
